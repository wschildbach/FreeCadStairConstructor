# -*- coding: utf-8 -*-

import Part, FreeCAD, math, PartGui, FreeCADGui, numpy, itertools
from FreeCAD import Base, Console

def ipol(x0,x,x1):
	"""Interpolate between x0 and x1"""
	return (1-x)*x0 + x* x1

class multiEdge:
	"""A class that mimics "Edge" behavior, given an array of Edges (which should preferrably join).
	
	With this, one can use a parameter between 0 and the total length of the edges, and call valueAt() and tangentAt().
	"""
	
	def __init__(self, sh):
		self.sh = sh
		self.lens = [ e.Length for e in sh.Edges ]
		self.fp = [e.FirstParameter for e in sh.Edges ]
		self.lp = [e.LastParameter for e in sh.Edges ]

		self.FirstParameter = 0
		self.LastParameter = sum(self.lens)
		self.Length = self.LastParameter

		# When converting sketches to Parts, some of the elements do not appear in natural order.
		# That is, the valueAt(lastParameter) is not equal to valueAt(firstParameter) of the following edge.
		# Therefore, we find that combination of reversals that makes them join up

		mi = float('+Infinity')
		for p in itertools.product(range(2), repeat=len(self.sh.Edges)):
			t = self.__epDist(p)
			if (t < mi):
				mi = t
				self.invert = p

	def __epDist(self,p):
		"""helper function that can be used as metric of how well p performs for inversions""" 
		t = 0
		for i in range(1,len(self.sh.Edges)):
			lastE = sh.Edges[i-1]
			thisE = sh.Edges[i]
			lastV = lastE.valueAt((lastE.FirstParameter, lastE.LastParameter)[1-p[i-1]])
			firstV = thisE.valueAt((thisE.FirstParameter, thisE.LastParameter)[p[i]])
			t += firstV.sub(lastV).Length
		return t

	def mapTo(self,x):
		"""map "global" parameter x into a tuple (edge,parameter on edge,inversion factor)"""

		t = 0
		# search that edge that x maps into
		for i in range(len(self.lens)):
			lastt = t
			t += self.lens[i]
			if (t > x): break

		# this is the edge that x maps into
		theEdge = self.sh.Edges[i]

		# map x into [0,1[
		x = (x-lastt)/self.lens[i]

		if (self.invert[i]):
			return (theEdge, ipol(theEdge.LastParameter,x,theEdge.FirstParameter), -1)
		else:
			return (theEdge, ipol(theEdge.FirstParameter,x,theEdge.LastParameter), 1)

	def valueAt(self, x):
		(e,xx,inv) = self.mapTo(x)
		return e.valueAt(xx)

	def tangentAt(self, x):
		(e,xx,inv) = self.mapTo(x)
		# make sure to flip the tangent if the edge is inverted
		return e.tangentAt(xx).multiply(inv)

def makeStairs(sh, nRisers, h=0, riseHeight=0, treadThickness = 0, riserHeight = 0, treadDepth = 0, treadWidth = 0):

	e = multiEdge(sh)
	defaultUnit = tu("1 mm") # so they say...
	
	# helper array for parameter taps
	val = numpy.linspace(e.FirstParameter,e.LastParameter,nRisers)

	# make sure we always follow the path uphill
	rev = (e.valueAt(val[nRisers-1]).z < e.valueAt(val[0]).z)
	if rev:
		val = val[::-1] # run parameter backwards

	# set up all default parameters 
	if h == 0:
		h = (e.valueAt(val[nRisers-1]).z - e.valueAt(val[0]).z) * defaultUnit

	if riseHeight == 0:
		riseHeight = h/nRisers

	if treadThickness == 0:
		treadThickness = riseHeight/10

	riserHeight = riseHeight - treadThickness

	if treadDepth == 0:
		treadDepth = 2*e.Length/float(nRisers-1)

	if treadWidth == 0:
		treadWidth = e.Length / 5

	print("h = {}, riseHeight = {}, treadThickness = {}, wid = {}, len = {}".format(h,riseHeight,treadThickness,treadWidth,treadDepth))

	shs  = []   # this will be a list of shapes, one for each step (a union of the riser and the tread)
	cuts = []   # a list of "cuts" which serve to cut away the part of the steps that reach under the next step

	z0 = e.valueAt(val[0]).z * defaultUnit

	for i in range(nRisers):
		sh = Part.makeBox(treadThickness,treadWidth,riserHeight,Base.Vector(0,-treadWidth/2,0))
		if i+1 < nRisers:
			shTread = Part.makeBox(treadDepth,treadWidth,treadThickness,Base.Vector(0,-treadWidth/2,riserHeight))
			sh = sh.fuse(shTread)

		p = e.valueAt(val[i])
		ts = e.tangentAt(val[i])
		if rev: ts.multiply(-1)

		m = FreeCAD.Matrix( ts.x,-ts.y,  0, p.x,
							ts.y, ts.x,  0, p.y,
							0,    0,     1, z0+float(i)*riseHeight,
							0,    0,     0, 1 )

		sh.transformShape(m)

		cut = Part.makeBox(treadDepth,2*treadWidth,riseHeight,Base.Vector(treadThickness,-treadWidth,-2*treadThickness))
		cut.transformShape(m)

		shs.append(sh)
		cuts.append(cut)

	treads = [] # this will be a list of "raw" treads (i.e. oversized)
	for i in range(nRisers):
		sh = shs[i]
		if i+1 < nRisers:
			sh = sh.cut(cuts[i+1])

		treads.append(sh)

	c = Part.Compound(treads)
	Part.show(c)

sel = FreeCADGui.Selection.getSelection() # " sel " contains the items selected
sh = sel[0].Shape

tu = FreeCAD.Units.parseQuantity

makeStairs(sh,20,tu("3 m"),treadWidth=tu("1.6m"))
